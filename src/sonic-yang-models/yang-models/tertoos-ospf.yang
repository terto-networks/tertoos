module tertoos-ospf {
    yang-version 1.1;
    namespace "http://tertoos.io/yang/tertoos-ospf";
    prefix tos_ospf;

    import ietf-inet-types {
        prefix inet;
    }

    organization
        "TertoOS";
    contact
        "TertoOS Maintainers <maintainers@tertoos.io>";
    description
        "TertoOS OSPFv2 schema covering the CONFIG_DB tables that
         sonic-frr-mgmt-framework's frrcfgd already consumes for FRR
         ospfd rendering. There is no upstream sonic-ospf*.yang; this
         module formalizes the leaf set that the TertoOS IOS-XR-style CLI
         writes via translate.go.

         Tables modelled:
           OSPFV2_ROUTER                            -- per-VRF instance.
           OSPFV2_ROUTER_AREA                       -- per-area config.
           OSPFV2_ROUTER_AREA_NETWORK               -- area network prefixes.
           OSPFV2_ROUTER_AREA_POLICY_ADDRESS_RANGE  -- area summarization.
           OSPFV2_ROUTER_DISTRIBUTE_ROUTE           -- redistribute.
           OSPFV2_ROUTER_PASSIVE_INTERFACE          -- passive-if list.
           OSPFV2_INTERFACE                         -- per-interface config.

         Coverage is intentionally a subset of frrcfgd's full key map --
         only the leaves the IOS-XR CLI emits are modelled. Additional
         leaves frrcfgd accepts (write-multiplier, max-metric variants,
         virtual-link, etc.) are out of S6 scope and may be added in
         later sprints.";

    revision 2026-04-27 {
        description "Initial revision (S6 — OSPFv2 IOS-XR CLI coverage).";
    }

    typedef ospf_log_adj_changes {
        type enumeration {
            enum default;
            enum detail;
        }
        description "log-adjacency-changes verbosity.";
    }

    typedef ospf_abr_type {
        type enumeration {
            enum cisco;
            enum ibm;
            enum shortcut;
            enum standard;
        }
    }

    typedef ospf_area_auth {
        type enumeration {
            enum none;
            enum text;
            enum message-digest;
        }
    }

    typedef ospf_area_shortcut {
        type enumeration {
            enum default;
            enum disable;
            enum enable;
        }
    }

    typedef ospf_network_type {
        type enumeration {
            enum point-to-point;
            enum broadcast;
            enum non-broadcast;
            enum point-to-multipoint;
        }
    }

    typedef ospf_redist_proto {
        type enumeration {
            enum connected;
            enum static;
            enum bgp;
            enum kernel;
        }
    }

    container tertoos-ospf {

        // -------- OSPFV2_ROUTER -------------------------------------------
        container OSPFV2_ROUTER {
            list OSPFV2_ROUTER_LIST {
                key "vrf_name";

                leaf vrf_name {
                    type string {
                        pattern '[A-Za-z][A-Za-z0-9_-]{0,63}|default';
                    }
                    description "VRF name (use 'default' for the default VRF).";
                }
                leaf enable {
                    type boolean;
                }
                leaf router-id {
                    type inet:ipv4-address;
                    description "OSPF router-id (4-byte dotted).";
                }
                leaf log-adjacency-changes {
                    type ospf_log_adj_changes;
                }
                leaf passive-interface-default {
                    type boolean;
                    description "All interfaces passive by default.";
                }
                leaf default-metric {
                    type uint32;
                }
                leaf abr-type {
                    type ospf_abr_type;
                }
                leaf distance-all {
                    type uint8 { range "1..255"; }
                }
                leaf distance-external {
                    type uint8 { range "1..255"; }
                }
                leaf distance-inter-area {
                    type uint8 { range "1..255"; }
                }
                leaf distance-intra-area {
                    type uint8 { range "1..255"; }
                }
                leaf auto-cost-reference-bandwidth {
                    type uint32 { range "1..4294967"; }
                    units "Mbps";
                }
                // S8 — Segment Routing globals (#24).
                leaf segment_routing      { type boolean; }
                leaf sr_global_block_lower { type uint32 { range "16..1048575"; } }
                leaf sr_global_block_upper { type uint32 { range "16..1048575"; } }
                leaf sr_local_block_lower  { type uint32 { range "16..1048575"; } }
                leaf sr_local_block_upper  { type uint32 { range "16..1048575"; } }
            }
        }

        // -------- OSPFV2_PREFIX_SID (S8 — #24) ----------------------------
        container OSPFV2_PREFIX_SID {
            list OSPFV2_PREFIX_SID_LIST {
                key "vrf_name prefix";
                leaf vrf_name { type string; }
                leaf prefix   { type inet:ip-prefix; }
                leaf index        { type uint32; }
                leaf explicit_null { type boolean; }
                leaf no_php       { type boolean; }
            }
        }

        // -------- OSPFV2_ROUTER_AREA --------------------------------------
        container OSPFV2_ROUTER_AREA {
            list OSPFV2_ROUTER_AREA_LIST {
                key "vrf_name area_id";

                leaf vrf_name {
                    type string;
                }
                leaf area_id {
                    type inet:ipv4-address;
                    description "Area id in dotted form (0.0.0.0 = backbone).";
                }
                leaf stub {
                    type boolean;
                }
                leaf stub-no-summary {
                    type boolean;
                }
                leaf stub-default-cost {
                    type uint32;
                }
                leaf authentication {
                    type ospf_area_auth;
                }
                leaf shortcut {
                    type ospf_area_shortcut;
                }
                leaf import-list {
                    type string;
                }
                leaf export-list {
                    type string;
                }
                leaf filter-list-in {
                    type string;
                }
                leaf filter-list-out {
                    type string;
                }
            }
        }

        // -------- OSPFV2_ROUTER_AREA_NETWORK ------------------------------
        container OSPFV2_ROUTER_AREA_NETWORK {
            description "Area network prefixes — key-only entries.";
            list OSPFV2_ROUTER_AREA_NETWORK_LIST {
                key "vrf_name area_id prefix";

                leaf vrf_name { type string; }
                leaf area_id  { type inet:ipv4-address; }
                leaf prefix   { type inet:ipv4-prefix; }
            }
        }

        // -------- OSPFV2_ROUTER_AREA_POLICY_ADDRESS_RANGE -----------------
        container OSPFV2_ROUTER_AREA_POLICY_ADDRESS_RANGE {
            list OSPFV2_ROUTER_AREA_POLICY_ADDRESS_RANGE_LIST {
                key "vrf_name area_id prefix";

                leaf vrf_name { type string; }
                leaf area_id  { type inet:ipv4-address; }
                leaf prefix   { type inet:ipv4-prefix; }
                leaf advertise {
                    type boolean;
                    default true;
                }
                leaf metric {
                    type uint32;
                }
                leaf substitue-prefix {
                    type inet:ipv4-prefix;
                    description
                        "Substitute prefix for area range (frrcfgd preserves
                         the upstream typo 'substitue').";
                }
            }
        }

        // -------- OSPFV2_ROUTER_DISTRIBUTE_ROUTE --------------------------
        container OSPFV2_ROUTER_DISTRIBUTE_ROUTE {
            list OSPFV2_ROUTER_DISTRIBUTE_ROUTE_LIST {
                key "vrf_name protocol";

                leaf vrf_name { type string; }
                leaf protocol { type ospf_redist_proto; }
                leaf metric   { type uint32; }
                leaf metric-type {
                    type uint8 { range "1..2"; }
                }
                leaf route-map {
                    type string;
                    description "Reference to a ROUTE_MAP_SET name.";
                }
                leaf always {
                    type boolean;
                    description "default-information originate always.";
                }
            }
        }

        // -------- OSPFV2_ROUTER_PASSIVE_INTERFACE -------------------------
        container OSPFV2_ROUTER_PASSIVE_INTERFACE {
            list OSPFV2_ROUTER_PASSIVE_INTERFACE_LIST {
                key "vrf_name interface";
                leaf vrf_name { type string; }
                leaf interface {
                    type string {
                        pattern '(Ethernet|PortChannel|Vlan|Loopback)[0-9]+(\\.[0-9]+)?';
                    }
                }
            }
        }

        // -------- OSPFV2_INTERFACE ----------------------------------------
        container OSPFV2_INTERFACE {
            list OSPFV2_INTERFACE_LIST {
                key "interface address";

                leaf interface {
                    type string {
                        pattern '(Ethernet|PortChannel|Vlan|Loopback)[0-9]+(\\.[0-9]+)?';
                    }
                }
                leaf address {
                    type string;
                    description
                        "IPv4 address scope for this OSPF interface entry, or
                         the literal 'null' for an interface-wide entry that
                         applies regardless of the configured IP.";
                }
                leaf area-id {
                    type inet:ipv4-address;
                }
                leaf metric {
                    type uint32 { range "1..65535"; }
                    description "OSPF cost (IOS-XR 'ip ospf cost').";
                }
                leaf hello-interval {
                    type uint16 { range "1..65535"; }
                    units "seconds";
                }
                leaf dead-interval {
                    type uint32 { range "1..65535"; }
                    units "seconds";
                }
                leaf network-type {
                    type ospf_network_type;
                }
                leaf priority {
                    type uint8;
                }
                leaf authentication-type {
                    type ospf_area_auth;
                }
                leaf authentication-key {
                    type string;
                }
                leaf authentication-key-id {
                    type uint8 { range "1..255"; }
                }
                leaf authentication-md5-key {
                    type string;
                }
                leaf retransmission-interval {
                    type uint16 { range "1..65535"; }
                    units "seconds";
                }
                leaf transmit-delay {
                    type uint16 { range "1..65535"; }
                    units "seconds";
                }
                leaf mtu-ignore {
                    type boolean;
                }
                leaf bfd-enable {
                    type boolean;
                }
            }
        }
    }
}
