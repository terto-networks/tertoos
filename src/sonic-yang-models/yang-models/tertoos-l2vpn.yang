module tertoos-l2vpn {
    yang-version 1.1;
    namespace "http://tertoos.io/yang/tertoos-l2vpn";
    prefix tos_l2vpn;

    import ietf-inet-types { prefix inet; }

    organization "TertoOS";
    contact "TertoOS Maintainers <maintainers@tertoos.io>";
    description
        "TertoOS L2VPN VPWS schema (P3 #29-#30). Cobre point-to-point
         pseudowire over MPLS (LDP signaling). VPLS (#31) e EVPN-MPLS
         (#37) ficam fora desta fatia.

         Tabelas:
           L2VPN_PW_CLASS       -- shared pseudowire parameters.
           L2VPN_XCONNECT_GROUP -- p2p attachments by group/p2p name.

         Backend = frrcfgd em sonic-frr-mgmt-framework (handlers e
         template ldpd.conf.db.l2vpn.j2 em S11).";

    revision 2026-04-27 {
        description "Initial S11 L2VPN VPWS schema.";
    }

    typedef pw_encapsulation {
        type enumeration {
            enum mpls;
        }
    }

    typedef pw_transport_mode {
        type enumeration {
            enum ethernet;
            enum vlan;
        }
    }

    container tertoos-l2vpn {

        container L2VPN_PW_CLASS {
            list L2VPN_PW_CLASS_LIST {
                key "name";
                leaf name { type string; }
                leaf encapsulation {
                    type pw_encapsulation;
                    default mpls;
                }
                leaf control-word { type boolean; }
                leaf mtu { type uint16 { range "64..9216"; } }
                leaf transport-mode {
                    type pw_transport_mode;
                    default ethernet;
                }
            }
        }

        container L2VPN_BRIDGE_DOMAIN {
            description "VPLS bridge-domain (S11.x).";
            list L2VPN_BRIDGE_DOMAIN_LIST {
                key "name";
                leaf name { type string { length "1..64"; } }
                leaf description              { type string; }
                leaf mac_aging                { type uint32; }
                leaf mac_limit                { type uint32; }
                leaf flooding_unknown_unicast { type boolean; }
                leaf flooding_broadcast       { type boolean; }
                leaf vfi_name                 { type string; }
            }
        }

        container L2VPN_VFI {
            description "VFI (Virtual Forwarding Instance) for VPLS.";
            list L2VPN_VFI_LIST {
                key "name";
                leaf name { type string { length "1..64"; } }
                leaf vpn_id           { type uint32; }
                leaf pw_class         { type string; }
                leaf manual_signaling { type boolean; }
                leaf autodiscovery_bgp { type boolean; }
                leaf route_distinguisher { type string; }
                leaf-list route_target_import { type string; }
                leaf-list route_target_export { type string; }
            }
        }

        container L2VPN_BD_AC {
            description "Attachment circuits per bridge-domain (membership-only).";
            list L2VPN_BD_AC_LIST {
                key "bd_name interface";
                leaf bd_name { type string; }
                leaf interface {
                    type string {
                        pattern '(Ethernet|PortChannel|Vlan|Loopback)[0-9]+(\\.[0-9]+)?';
                    }
                }
            }
        }

        container L2VPN_BD_NEIGHBOR {
            description "Per-peer pseudowire entries within a manual VFI.";
            list L2VPN_BD_NEIGHBOR_LIST {
                key "vfi_name peer_address";
                leaf vfi_name     { type string; }
                leaf peer_address { type inet:ip-address; }
                leaf pw_id        { type uint32 { range "1..4294967295"; } }
                leaf pw_class     { type string; }
            }
        }

        container L2VPN_XCONNECT_GROUP {
            description
                "Each entry is one p2p pseudowire (group/p2p tuple).
                 The IOS-XR `l2vpn xconnect group <g> p2p <p>` block
                 maps directly to one row keyed (group_name, p2p_name).";
            list L2VPN_XCONNECT_GROUP_LIST {
                key "group_name p2p_name";
                leaf group_name { type string; }
                leaf p2p_name { type string; }
                leaf interface {
                    type string {
                        pattern '(Ethernet|PortChannel|Vlan|Loopback)[0-9]+(\\.[0-9]+)?';
                    }
                }
                leaf peer-address { type inet:ip-address; }
                leaf pw-id { type uint32 { range "1..4294967295"; } }
                leaf pw-class {
                    type leafref {
                        path "/tertoos-l2vpn/L2VPN_PW_CLASS/L2VPN_PW_CLASS_LIST/name";
                    }
                }
                leaf mtu { type uint16 { range "64..9216"; } }
                leaf enabled {
                    type boolean;
                    default true;
                }
            }
        }

    }
}
